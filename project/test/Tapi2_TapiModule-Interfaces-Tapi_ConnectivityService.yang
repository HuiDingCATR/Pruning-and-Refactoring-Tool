module TapiModule-Interfaces-Tapi_ConnectivityService {
    namespace "urn:ONF:TapiModule-Interfaces-Tapi_ConnectivityService";
    prefix TapiModule-Interfaces-Tapi_ConnectivityService;
    import TapiModule-ObjectClasses {
        prefix TapiModule-ObjectClasses;
    }
    import TapiModule-TypeDefinitions {
        prefix TapiModule-TypeDefinitions;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-05-27 {
        description "Latest revision";
        reference "RFC 6020 and RFC 6087";
    }
    rpc getConnectionDetails {
        description "none";
        input {
            leaf serviceIdOrName {
                type string;
                description "none";
            }
            leaf connectionIdOrName {
                type string;
                description "none";
            }
        }
        output {
            container connection {
                uses TapiModule-ObjectClasses:Tapi_Connection;
                description "none";
            }
        }
    }
    rpc getConnectivityServiceList {
        description "none";
        output {
            list serviceList {
                uses TapiModule-ObjectClasses:Tapi_ConnectivityService;
                description "none";
            }
        }
    }
    rpc getConnectionEndPointDetails {
        description "none";
        input {
            leaf serviceIdOrName {
                type string;
                description "none";
            }
            leaf connectionIdOrName {
                type string;
                description "none";
            }
            leaf connEPIdOrName {
                type string;
                description "none";
            }
        }
        output {
            container connEP {
                uses TapiModule-ObjectClasses:Tapi_ConnectionEndPoint;
                description "none";
            }
        }
    }
    rpc getServiceEndPointDetails {
        description "none";
        input {
            leaf serviceEPIdOrName {
                type string;
                description "none";
            }
        }
        output {
            container serviceEP {
                uses TapiModule-ObjectClasses:Tapi_ServiceEndPoint;
                description "none";
            }
        }
    }
    rpc getConnectivityServiceDetails {
        description "none";
        input {
            leaf serviceIdOrName {
                type string;
                description "none";
            }
        }
        output {
            container service {
                uses TapiModule-ObjectClasses:Tapi_ConnectivityService;
                description "none";
            }
        }
    }
    rpc getServiceEndPointList {
        description "none";
        output {
            list serviceEPList {
                uses TapiModule-ObjectClasses:Tapi_ServiceEndPoint;
                description "none";
            }
        }
    }
    rpc createConnectivityService {
        description "none";
        input {
            list servicePort {
                min-elements 2;
                uses TapiModule-ObjectClasses:Tapi_ServicePort;
                description "none";
            }
            container connConstraint {
                uses TapiModule-TypeDefinitions:Tapi_ConnectivityConstraint;
                description "none";
            }
            container connSchedule {
                uses TapiModule-TypeDefinitions:Tapi_ScheduleInfo;
                description "none";
            }
        }
        output {
            container connService {
                uses TapiModule-ObjectClasses:Tapi_ConnectivityService;
                description "none";
            }
        }
    }
    rpc updateConnectivityService {
        description "none";
        input {
            leaf serviceIdOrName {
                type string;
                description "none";
            }
            container connConstraint {
                uses TapiModule-TypeDefinitions:Tapi_ConnectivityConstraint;
                description "none";
            }
            container connSchedule {
                uses TapiModule-TypeDefinitions:Tapi_ScheduleInfo;
                description "none";
            }
        }
        output {
            container connService {
                uses TapiModule-ObjectClasses:Tapi_ConnectivityService;
                description "none";
            }
        }
    }
    rpc deleteConnectivityService {
        description "none";
        input {
            leaf serviceIdOrName {
                type string;
                description "none";
            }
        }
        output {
            container connService {
                uses TapiModule-ObjectClasses:Tapi_ConnectivityService;
                description "none";
            }
        }
    }
}
