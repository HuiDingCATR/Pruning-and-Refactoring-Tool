module TapiModule-Interfaces-Tapi_PathComputationService {
    namespace "urn:ONF:TapiModule-Interfaces-Tapi_PathComputationService";
    prefix TapiModule-Interfaces-Tapi_PathComputationService;
    import TapiModule-ObjectClasses {
        prefix TapiModule-ObjectClasses;
    }
    import TapiModule-TypeDefinitions {
        prefix TapiModule-TypeDefinitions;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-05-27 {
        description "Latest revision";
        reference "RFC 6020 and RFC 6087";
    }
    rpc computeP2PPath {
        description "none";
        input {
            list servicePort {
                min-elements 2;
                max-elements 2;
                uses TapiModule-ObjectClasses:Tapi_ServicePort;
                description "none";
            }
            container routingConstraint {
                uses TapiModule-TypeDefinitions:Tapi_ConnectivityConstraint;
                description "none";
            }
            container objectiveFunction {
                uses TapiModule-TypeDefinitions:Tapi_PathObjectiveFunction;
                description "none";
            }
        }
        output {
            list path {
                min-elements 1;
                uses TapiModule-ObjectClasses:Tapi_Path;
                description "none";
            }
        }
    }
    rpc optimizeP2PPath {
        description "none";
        input {
            leaf pathIdOrName {
                type string;
                description "none";
            }
            container routingConstraint {
                uses TapiModule-TypeDefinitions:Tapi_ConnectivityConstraint;
                description "none";
            }
            container optimizationConstraint {
                uses TapiModule-TypeDefinitions:Tapi_PathOptimizationConstraint;
                description "none";
            }
            container objectiveFunction {
                uses TapiModule-TypeDefinitions:Tapi_PathObjectiveFunction;
                description "none";
            }
        }
        output {
            list path {
                min-elements 1;
                uses TapiModule-ObjectClasses:Tapi_Path;
                description "none";
            }
        }
    }
}
