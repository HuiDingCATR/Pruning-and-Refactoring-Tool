module TapiModule-Interfaces-Tapi_TopologyService {
    namespace "urn:ONF:TapiModule-Interfaces-Tapi_TopologyService";
    prefix TapiModule-Interfaces-Tapi_TopologyService;
    import TapiModule-ObjectClasses {
        prefix TapiModule-ObjectClasses;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-05-27 {
        description "Latest revision";
        reference "RFC 6020 and RFC 6087";
    }
    rpc getTopologyDetails {
        description "none";
        input {
            leaf topologyIdOrName {
                type string;
                description "none";
            }
        }
        output {
            container topology {
                uses TapiModule-ObjectClasses:Tapi_Topology;
                description "none";
            }
        }
    }
    rpc getNodeDetails {
        description "none";
        input {
            leaf topologyIdOrName {
                type string;
                description "none";
            }
            leaf nodeIdOrName {
                type string;
                description "none";
            }
        }
        output {
            container node {
                uses TapiModule-ObjectClasses:Tapi_Node;
                description "none";
            }
        }
    }
    rpc getNodeEdgePointDetails {
        description "none";
        input {
            leaf topologyIdOrName {
                type string;
                description "none";
            }
            leaf nodeIdOrName {
                type string;
                description "none";
            }
            leaf epIdOrName {
                type string;
                description "none";
            }
        }
        output {
            container nodeEdgePoint {
                uses TapiModule-ObjectClasses:Tapi_NodeEdgePoint;
                description "none";
            }
        }
    }
    rpc getLinkDetails {
        description "none";
        input {
            leaf topologyIdOrName {
                type string;
                description "none";
            }
            leaf linkIdOrName {
                type string;
                description "none";
            }
        }
        output {
            container link {
                uses TapiModule-ObjectClasses:Tapi_Link;
                description "none";
            }
        }
    }
}
